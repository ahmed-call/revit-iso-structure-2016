(defun c:totarc()
(setq as"Select Objects To Calculate ")
(princ as)

;(aaa)
(setq ss(ssget))
  (setq ss1(sslength ss))
  (setq k -1)
  (setq sum 0)
  (repeat ss1
  (setq k(+ k 1))
  (setq n(ssname ss k))
  (setq e(entget n))
(if(setq pt2(cdr(assoc 11 e)))
  (progn
  (setq pt1(cdr(assoc 10 e)))
  (setq l(distance pt1 pt2))
)
)
(if(setq ea(cdr(assoc 51 e)))
  (progn
  (setq r(cdr(assoc 40 e)))
  (setq sa(cdr(assoc 50 e)))
(if(< ea sa)
  (setq ea(+ ea 6.28319))
)
  (setq rad(- ea sa))
  (setq l(* r rad))
)
)
  (setq sum(+ sum l))
)
(princ "\n The Total Length = ")
(princ sum)
(prin1)
)


(defun aaa()
 (setq aa(ssget))
(command ".copy" aa "" '(0 0 0)'(0 0 0))
(command "explode" aa)
(setq ss(ssget "p"))
(command "erase" "p" "")
)
