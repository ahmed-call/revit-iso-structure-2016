;                              -: WELL COME TO GC-HVAC BLOCKS LSP:-      

(defun C:246S()
     (princ "IKRAM:-")
     (command ".INSERT" "24x6S" "MID"))

(defun C:GV25()
     (princ "IKRAM:-")
     (command ".INSERT" "GV25" "MID"))

(defun C:246R()
     (princ "IKRAM:-")
     (command ".INSERT" "24x6R" "MID"))

(defun C:486R1S()
     (princ "IKRAM:-")
     (command ".INSERT" "48x6R-1S" "MID"))

(defun C:486R2S()
     (princ "IKRAM:-")
     (command ".INSERT" "48x6R-2S" "MID"))

(defun C:486R3S()
     (princ "IKRAM:-")
     (command ".INSERT" "48x6R-3S" "MID"))

(defun C:486R4S()
     (princ "IKRAM:-")
     (command ".INSERT" "48x6R-4S" "MID"))

(defun C:486S1S()
     (princ "IKRAM:-")
     (command ".INSERT" "48x6S-1S" "MID"))

(defun C:486S2S()
     (princ "IKRAM:-")
     (command ".INSERT" "48x6S-2S" "MID"))

(defun C:486S3S()
     (princ "IKRAM:-")
     (command ".INSERT" "48x6S-3S" "MID"))

(defun C:486S4S()
     (princ "IKRAM:-")
     (command ".INSERT" "48x6S-4S" "MID"))

(defun C:D6()
     (princ "IKRAM:-")
     (command ".INSERT" "D6" "MID"))

(defun C:FT1()
     (princ "IKRAM:-")
     (command ".INSERT" "FT1" "MID"))

(defun C:09mk904()
     (princ "IKRAM:-")
     (command ".INSERT" "09mk904" "MID"))

(defun C:09mk903()
     (princ "IKRAM:-")
     (command ".INSERT" "09mk903" "MID"))

(defun C:09mk906()
     (princ "IKRAM:-")
     (command ".INSERT" "09mk906" "MID"))

(defun C:09mk907()
     (princ "IKRAM:-")
     (command ".INSERT" "09mk907" "MID"))

(defun C:09mk908()
     (princ "IKRAM:-")
     (command ".INSERT" "09mk908" "MID"))

(defun C:09mk910()
     (princ "IKRAM:-")
     (command ".INSERT" "09mk910" "MID"))

(defun C:09mk914()
     (princ "IKRAM:-")
     (command ".INSERT" "09mk914" "MID"))

(defun C:09mk912()
     (princ "IKRAM:-")
     (command ".INSERT" "09mk912" "MID"))

(defun C:07mkD06()
     (princ "IKRAM:-")
     (command ".INSERT" "07mkD06" "MID"))

(defun C:07mkD10()
     (princ "IKRAM:-")
     (command ".INSERT" "07mkD10" "MID"))

(defun C:07mkD12()
     (princ "IKRAM:-")
     (command ".INSERT" "07mkD12" "MID"))

(defun C:07mkD14()
     (princ "IKRAM:-")
     (command ".INSERT" "07mkD14" "MID"))

(defun C:07mkD18()
     (princ "IKRAM:-")
     (command ".INSERT" "07mkD18" "MID"))

(defun C:07mkD20()
     (princ "IKRAM:-")
     (command ".INSERT" "07mkD20" "MID"))

(defun C:07mke12()
     (princ "IKRAM:-")
     (command ".INSERT" "07mke12" "MID"))

(defun C:UTC60()
     (princ "IKRAM:-")
     (command ".INSERT" "UTC60" "MID"))

(defun C:UTC50()
     (princ "IKRAM:-")
     (command ".INSERT" "UTC50" "MID"))

(defun C:UTC40()
     (princ "IKRAM:-")
     (command ".INSERT" "UTC40" "MID"))

(defun C:AROW()
     (princ "IKRAM:-")
     (command ".INSERT" "AROW" "MID"))

(defun C:D9()
     (princ "IKRAM:-")
     (command ".INSERT" "D9" "MID"))

(defun C:D12()
     (princ "IKRAM:-")
     (command ".INSERT" "D12" "MID"))

(defun C:D15()
     (princ "IKRAM:-")
     (command ".INSERT" "D15" "MID"))

(defun C:D18()
     (princ "IKRAM:-")
     (command ".INSERT" "D18" "MID"))

(defun C:rwo()
     (princ "IKRAM:-")
     (command ".INSERT" "RWo" "MID"))

(defun C:D21()
     (princ "IKRAM:-")
     (command ".INSERT" "D21" "MID"))

(defun C:D24()
     (princ "IKRAM:-")
     (command ".INSERT" "D24" "MID"))

(defun C:R6()
     (princ "IKRAM:-")
     (command ".INSERT" "R6" "MID"))

(defun C:R9()
     (princ "IKRAM:-")
     (command ".INSERT" "R9" "MID"))

(defun C:R12()
     (princ "IKRAM:-")
     (command ".INSERT" "R12" "MID"))

(defun C:R15()
     (princ "IKRAM:-")
     (command ".INSERT" "R15" "MID"))

(defun C:R18()
     (princ "IKRAM:-")
     (command ".INSERT" "R18" "MID"))

(defun C:R21()
     (princ "IKRAM:-")
     (command ".INSERT" "R21" "MID"))

(defun C:R24()
     (princ "IKRAM:-")
     (command ".INSERT" "R24" "MID"))

(defun C:126()
     (princ "IKRAM:-")
     (command ".INSERT" "G12x6" "MID"))

(defun C:128()
     (princ "IKRAM:-")
     (command ".INSERT" "G12x8" "MID"))

(defun C:166()
     (princ "IKRAM:-")
     (command ".INSERT" "G16x6" "MID"))

(defun C:186()
     (princ "IKRAM:-")
     (command ".INSERT" "G18x6" "MID"))

(defun C:188()
     (princ "IKRAM:-")
     (command ".INSERT" "G18x8" "MID"))

(defun C:1810()
     (princ "IKRAM:-")
     (command ".INSERT" "G18x10" "MID"))

(defun C:1812()
     (princ "IKRAM:-")
     (command ".INSERT" "G18x12" "MID"))

(defun C:1814()
     (princ "IKRAM:-")
     (command ".INSERT" "G18x14" "MID"))

(defun C:206()
     (princ "IKRAM:-")
     (command ".INSERT" "G20x6" "MID"))

(defun C:208()
     (princ "IKRAM:-")
     (command ".INSERT" "G20x8" "MID"))

(defun C:2010()
     (princ "IKRAM:-")
     (command ".INSERT" "G20x10" "MID"))

(defun C:2012()
     (princ "IKRAM:-")
     (command ".INSERT" "G20x12" "MID"))

(defun C:2014()
     (princ "IKRAM:-")
     (command ".INSERT" "G20x14" "MID"))

(defun C:2016()
     (princ "IKRAM:-")
     (command ".INSERT" "G20x16" "MID"))

(defun C:2018()
     (princ "IKRAM:-")
     (command ".INSERT" "G20x18" "MID"))

(defun C:248()
     (princ "IKRAM:-")
     (command ".INSERT" "G24x8" "MID"))

(defun C:2410()
     (princ "IKRAM:-")
     (command ".INSERT" "G24x10" "MID"))

(defun C:2412()
     (princ "IKRAM:-")
     (command ".INSERT" "G24x12" "MID"))

(defun C:2414()
     (princ "IKRAM:-")
     (command ".INSERT" "G24x14" "MID"))

(defun C:2418()
     (princ "IKRAM:-")
     (command ".INSERT" "G24x18" "MID"))

(defun C:306()
     (princ "IKRAM:-")
     (command ".INSERT" "G30x6" "MID"))

(defun C:308()
     (princ "IKRAM:-")
     (command ".INSERT" "G30x8" "MID"))

(defun C:3010()
     (princ "IKRAM:-")
     (command ".INSERT" "G30x10" "MID"))

(defun C:3012()
     (princ "IKRAM:-")
     (command ".INSERT" "G30x12" "MID"))

(defun C:3014()
     (princ "IKRAM:-")
     (command ".INSERT" "G30x14" "MID"))

(defun C:3018()
     (princ "IKRAM:-")
     (command ".INSERT" "G30x18" "MID"))

(defun C:3020()
     (princ "IKRAM:-")
     (command ".INSERT" "G30x20" "MID"))

(defun C:3024()
     (princ "IKRAM:-")
     (command ".INSERT" "G30x24" "MID"))

(defun C:368()
     (princ "IKRAM:-")
     (command ".INSERT" "G36x8" "MID"))

(defun C:3610()
     (princ "IKRAM:-")
     (command ".INSERT" "G36x10" "MID"))

(defun C:3612()
     (princ "IKRAM:-")
     (command ".INSERT" "G36x12" "MID"))

(defun C:3614()
     (princ "IKRAM:-")
     (command ".INSERT" "G36x14" "MID"))

(defun C:3618()
     (princ "IKRAM:-")
     (command ".INSERT" "G36x18" "MID"))

(defun C:3620()
     (princ "IKRAM:-")
     (command ".INSERT" "G36x20" "MID"))

(defun C:3624()
     (princ "IKRAM:-")
     (command ".INSERT" "G36x24" "MID"))

(defun C:4824()
     (princ "IKRAM:-")
     (command ".INSERT" "G48x24" "MID"))

(defun C:4836()
     (princ "IKRAM:-")
     (command ".INSERT" "G48x36" "MID"))

(defun C:RG12()
     (princ "IKRAM:-")
     (command ".INSERT" "RAG12" "NEA"))

(defun C:RG16()
     (princ "IKRAM:-")
     (command ".INSERT" "RAG16" "NEA"))

(defun C:RG18()
     (princ "IKRAM:-")
     (command ".INSERT" "RAG18" "NEA"))

(defun C:RG20()
     (princ "IKRAM:-")
     (command ".INSERT" "RAG20" "NEA"))

(defun C:RG24()
     (princ "IKRAM:-")
     (command ".INSERT" "RAG24" "NEA"))

(defun C:RG30()
     (princ "IKRAM:-")
     (command ".INSERT" "RAG30" "NEA"))

(defun C:RG36()
     (princ "IKRAM:-")
     (command ".INSERT" "RAG36" "NEA"))

(defun C:RG40()
     (princ "IKRAM:-")
     (command ".INSERT" "RAG40" "NEA"))

(defun C:RG48()
     (princ "IKRAM:-")
     (command ".INSERT" "RAG48" "NEA"))

(defun C:SG12()
     (princ "IKRAM:-")
     (command ".INSERT" "SAG12" "NEA"))

(defun C:SG16()
     (princ "IKRAM:-")
     (command ".INSERT" "SAG16" "NEA"))

(defun C:SG18()
     (princ "IKRAM:-")
     (command ".INSERT" "SAG18" "NEA"))

(defun C:SG20()
     (princ "IKRAM:-")
     (command ".INSERT" "SAG20" "NEA"))

(defun C:SG24()
     (princ "IKRAM:-")
     (command ".INSERT" "SAG24" "NEA"))

(defun C:SG30()
     (princ "IKRAM:-")
     (command ".INSERT" "SAG30" "NEA"))

(defun C:SG36()
     (princ "IKRAM:-")
     (command ".INSERT" "SAG36" "NEA"))

(defun C:SG40()
     (princ "IKRAM:-")
     (command ".INSERT" "SAG40" "NEA"))

(defun C:SG48()
     (princ "IKRAM:-")
     (command ".INSERT" "SAG48" "NEA"))

(defun C:JFD()
     (princ "IKRAM:-")
     (command ".INSERT" "JFD" "NEA"))

(defun C:LFD24()
     (princ "IKRAM:-")
     (command ".INSERT" "LFD24" "MID"))

(defun C:LFD48()
     (princ "IKRAM:-")
     (command ".INSERT" "LFD48" "MID"))

(defun C:HORD()
     (princ "IKRAM:-")
     (command ".INSERT" "HORD"))

(defun C:Pracd9()
     (princ "IKRAM:-")
     (command ".INSERT" "Pracd9" "MID"))

(defun C:Pracd12()
     (princ "IKRAM:-")
     (command ".INSERT" "Pracd12" "MID"))

(defun C:Pracd15()
     (princ "IKRAM:-")
     (command ".INSERT" "Pracd15" "MID"))

(defun C:Pracd18()
     (princ "IKRAM:-")
     (command ".INSERT" "Pracd18" "MID"))

(defun C:Pracd21()
     (princ "IKRAM:-")
     (command ".INSERT" "Pracd21" "MID"))

(defun C:Pracd24()
     (princ "IKRAM:-")
     (command ".INSERT" "Pracd24" "MID"))

(defun C:Prad6()
     (princ "IKRAM:-")
     (command ".INSERT" "Prad6" "MID"))

(defun C:Prad9()
     (princ "IKRAM:-")
     (command ".INSERT" "Prad9" "MID"))

(defun C:Prad12()
     (princ "IKRAM:-")
     (command ".INSERT" "Prad12" "MID"))

(defun C:Prad15()
     (princ "IKRAM:-")
     (command ".INSERT" "Prad15" "MID"))

(defun C:Psacd9()
     (princ "IKRAM:-")
     (command ".INSERT" "Psacd9" "MID"))

(defun C:Psacd12()
     (princ "IKRAM:-")
     (command ".INSERT" "Psacd12" "MID"))

(defun C:Psacd15()
     (princ "IKRAM:-")
     (command ".INSERT" "Psacd15" "MID"))

(defun C:Psacd18()
     (princ "IKRAM:-")
     (command ".INSERT" "Psacd18" "MID"))

(defun C:Psacd21()
     (princ "IKRAM:-")
     (command ".INSERT" "Psacd21" "MID"))

(defun C:Psacd24()
     (princ "IKRAM:-")
     (command ".INSERT" "Psacd24" "MID"))

(defun C:Psad6()
     (princ "IKRAM:-")
     (command ".INSERT" "Psad6" "MID"))

(defun C:Psad9()
     (princ "IKRAM:-")
     (command ".INSERT" "Psad9" "MID"))

(defun C:Psad12()
     (princ "IKRAM:-")
     (command ".INSERT" "Psad12" "MID"))

(defun C:Psad15()
     (princ "IKRAM:-")
     (command ".INSERT" "Psad15" "MID"))

(defun C:AC()
     (princ "IKRAM:-")
     (command ".INSERT" "AC" "NEA"))

(defun C:AD()
     (princ "Fadi:-")
     (command ".INSERT" "AD" "NEA"))

(defun C:ADSD1()
     (princ "IKRAM:-")
     (command ".INSERT" "ADSD1" "MID"))

(defun C:ADSD2()
     (princ "IKRAM:-")
     (command ".INSERT" "ADSD2" "MID"))

(defun C:AFV()
     (princ "IKRAM:-")
     (command ".INSERT" "AFV" "END"))

(defun C:AHU()
     (princ "IKRAM:-")
     (command ".INSERT" "AHU"))

(defun C:AFlx1()
     (princ "IKRAM:-")
     (command ".INSERT" "Ahu-Flx1" "MID"))

(defun C:AFlx2()
     (princ "IKRAM:-")
     (command ".INSERT" "Ahu-Flx2" "MID"))

(defun C:APF()
     (princ "IKRAM:-")
     (command ".INSERT" "APF1" "NEA"))
         
(defun C:ATP()
     (princ "IKRAM:-")
     (command ".INSERT" "ATP" "NEA"))

(defun C:CH1()
     (princ "IKRAM:-")
     (command ".INSERT" "CH1"))

(defun C:CH2()
     (princ "IKRAM:-")
     (command ".INSERT" "CH2"))

(defun C:CH3()
     (princ "IKRAM:-")
     (command ".INSERT" "CH3"))

(defun C:CUS()
     (princ "IKRAM:-")
     (command ".INSERT" "Cu-s"))

(defun C:CUT()
     (princ "IKRAM:-")
     (command ".INSERT" "Cu-t"))

(defun C:EV4()
     (princ "IKRAM:-")
     (command ".INSERT" "EV4" "NEA"))

(defun C:EV5()
     (princ "IKRAM:-")
     (command ".INSERT" "EV5" "NEA"))

(defun C:EV6()
     (princ "IKRAM:-")
     (command ".INSERT" "EV6" "NEA"))

(defun C:EV8()
     (princ "IKRAM:-")
     (command ".INSERT" "EV8" "NEA"))

(defun C:FAU()
     (princ "IKRAM:-")
     (command ".INSERT" "FAU"))

(defun C:FCCT()
     (princ "IKRAM:-")
     (command ".INSERT" "Fcu-Ct" "NEA"))

(defun C:FCDX()
     (princ "IKRAM:-")
     (command ".INSERT" "Fcu-Dx" "NEA"))

(defun C:FFlx1()
     (princ "IKRAM:-")
     (command ".INSERT" "Fcu-Flx1" "MID"))

(defun C:FFlx2()
     (princ "IKRAM:-")
     (command ".INSERT" "Fcu-Flx2" "MID"))

(defun C:FCN()
     (princ "IKRAM:-")
     (command ".INSERT" "Fcu-N" "MID"))

(defun C:HWB1()
     (princ "IKRAM:-")
     (command ".INSERT" "HWB-1"))

(defun C:HWB1()
     (princ "IKRAM:-")
     (command ".INSERT" "HWB-1"))

(defun C:NRD()
     (princ "IKRAM:-")
     (command ".INSERT" "NRD" "NEA"))

(defun C:EAV()
     (princ "IKRAM:-")
     (command ".INSERT" "EAV" "NEA"))

(defun C:VAV()
     (princ "IKRAM:-")
     (command ".INSERT" "VAV" "END"))

(defun C:VAVR()
     (princ "IKRAM:-")
     (command ".INSERT" "VAVR" "END"))

(defun C:VCD-2()
     (princ "IKRAM:-")
     (command ".INSERT" "VCD-2" "NEA"))

(defun C:FD-2()
     (princ "IKRAM:-")
     (command ".INSERT" "FD-2" "NEA"))

(defun C:VCD()
     (princ "IKRAM:-")
     (command ".INSERT" "VCD" "NEA"))

(defun C:EDH()
     (princ "IKRAM:-")
     (command ".INSERT" "EDH" "NEA"))

(defun C:RMF()
     (princ "IKRAM:-")
     (command ".INSERT" "RMF"))

(defun C:EAD()
     (princ "IKRAM:-")
     (command ".INSERT" "EAD"))

(defun C:FAD()
     (princ "IKRAM:-")
     (command ".INSERT" "FAD"))

(defun C:SAD()
     (princ "IKRAM:-")
     (command ".INSERT" "SAD"))

(defun C:RAD()
     (princ "IKRAM:-")
     (command ".INSERT" "RAD"))

(defun C:SAT()
     (princ "IKRAM:-")
     (command ".INSERT" "SAT" "NAE"))

(defun C:CT()
     (princ "IKRAM:-")
     (command ".INSERT" "CT"))

(defun C:PAC()
     (princ "IKRAM:-")
     (command ".INSERT" "PAC"))

(defun C:RALD()
     (princ "IKRAM:-")
     (command ".INSERT" "RALD"))

(defun C:SALD()
     (princ "IKRAM:-")
     (command ".INSERT" "SALD"))

(defun C:TXT()
     (princ "IKRAM:-")
     (command ".INSERT" "TXT"))

(defun C:VCD()
     (princ "IKRAM:-")
     (command ".INSERT" "VCD" "NEA"))

(defun C:DG()
     (princ "IKRAM:-")
     (command ".INSERT" "DG" "MID"))

(defun C:DG1()
     (princ "IKRAM:-")
     (command ".INSERT" "DG1" "MID"))

(defun C:UCL()
     (princ "IKRAM:-")
     (command ".INSERT" "UCL"))

(defun C:UCR()
     (princ "IKRAM:-")
     (command ".INSERT" "UCR"))

(defun C:LNT()
     (princ "IKRAM:-")
     (command ".INSERT" "LNT"))

(defun C:DFT()
     (princ "IKRAM:-")
     (command ".INSERT" "DFT"))

(defun C:FAIL()
     (princ "IKRAM:-")
     (command ".INSERT" "FAIL"))

(defun C:EAL()
     (princ "IKRAM:-")
     (command ".INSERT" "EAL"))

(defun C:CHWP()
     (princ "IKRAM:-")
     (command ".INSERT" "PUPMS"))

(defun C:EF()
     (princ "IKRAM:-")
     (command ".INSERT" "EF" "NEA"))

(defun C:SEF()
     (princ "IKRAM:-")
     (command ".INSERT" "SEF1" "NEA"))

(defun C:SSF()
     (princ "IKRAM:-")
     (command ".INSERT" "SSF1" "NEA"))

(defun C:UP25()
     (princ "IKRAM:-")
     (command ".INSERT" "UP25" "NEA"))

(defun C:UP32()
     (princ "IKRAM:-")
     (command ".INSERT" "UP32" "NEA"))

(defun C:UP40()
     (princ "IKRAM:-")
     (command ".INSERT" "UP40" "NEA"))

(defun C:UP50()
     (princ "IKRAM:-")
     (command ".INSERT" "UP50" "NEA"))

(defun C:UP65()
     (princ "IKRAM:-")
     (command ".INSERT" "UP65" "NEA"))

(defun C:UP75()
     (princ "IKRAM:-")
     (command ".INSERT" "UP75" "NEA"))

(defun C:UP100()
     (princ "IKRAM:-")
     (command ".INSERT" "UP100" "NEA"))

(defun C:UP125()
     (princ "IKRAM:-")
     (command ".INSERT" "UP125" "NEA"))

(defun C:UP150()
     (princ "IKRAM:-")
     (command ".INSERT" "UP150" "NEA"))

(defun C:UP200()
     (princ "IKRAM:-")
     (command ".INSERT" "UP200" "NEA"))

(defun C:UP250()
     (princ "IKRAM:-")
     (command ".INSERT" "UP250" "NEA"))

(defun C:DN25()
     (princ "IKRAM:-")
     (command ".INSERT" "DN25" "NEA"))

(defun C:DN32()
     (princ "IKRAM:-")
     (command ".INSERT" "DN32" "NEA"))

(defun C:DN40()
     (princ "IKRAM:-")
     (command ".INSERT" "DN40" "NEA"))

(defun C:DN50()
     (princ "IKRAM:-")
     (command ".INSERT" "DN50" "NEA"))

(defun C:DN65()
     (princ "IKRAM:-")
     (command ".INSERT" "DN65" "NEA"))

(defun C:DN75()
     (princ "IKRAM:-")
     (command ".INSERT" "DN75" "NEA"))

(defun C:DN100()
     (princ "IKRAM:-")
     (command ".INSERT" "DN100" "NEA"))

(defun C:DN125()
     (princ "IKRAM:-")
     (command ".INSERT" "DN125" "NEA"))

(defun C:DN150()
     (princ "IKRAM:-")
     (command ".INSERT" "DN150" "NEA"))

(defun C:DN200()
     (princ "IKRAM:-")
     (command ".INSERT" "DN200" "NEA"))

(defun C:DN250()
     (princ "IKRAM:-")
     (command ".INSERT" "DN250" "NEA"))

(defun C:DU25()
     (princ "IKRAM:-")
     (command ".INSERT" "DU25" "NEA"))

(defun C:DU32()
     (princ "IKRAM:-")
     (command ".INSERT" "DU332" "NEA"))

(defun C:DU40()
     (princ "IKRAM:-")
     (command ".INSERT" "DU40" "NEA"))

(defun C:DU50()
     (princ "IKRAM:-")
     (command ".INSERT" "DU50" "NEA"))

(defun C:DU65()
     (princ "IKRAM:-")
     (command ".INSERT" "DU65" "NEA"))

(defun C:DU75()
     (princ "IKRAM:-")
     (command ".INSERT" "DU75" "NEA"))

(defun C:DU100()
     (princ "IKRAM:-")
     (command ".INSERT" "DU100" "NEA"))

(defun C:DU125()
     (princ "IKRAM:-")
     (command ".INSERT" "DU125" "NEA"))

(defun C:DU150()
     (princ "IKRAM:-")
     (command ".INSERT" "DU150" "NEA"))

(defun C:DU200()
     (princ "IKRAM:-")
     (command ".INSERT" "DU200" "NEA"))

(defun C:DU250()
     (princ "IKRAM:-")
     (command ".INSERT" "DU250" "NEA"))

(defun C:TEE25()
     (princ "IKRAM:-")
     (command ".INSERT" "TEE25" "NEA"))

(defun C:TEE32()
     (princ "IKRAM:-")
     (command ".INSERT" "TEE332" "NEA"))

(defun C:TEE40()
     (princ "IKRAM:-")
     (command ".INSERT" "TEE40" "NEA"))

(defun C:TEE50()
     (princ "IKRAM:-")
     (command ".INSERT" "TEE50" "NEA"))

(defun C:TEE65()
     (princ "IKRAM:-")
     (command ".INSERT" "TEE65" "NEA"))

(defun C:TEE75()
     (princ "IKRAM:-")
     (command ".INSERT" "TEE75" "NEA"))

(defun C:TEE100()
     (princ "IKRAM:-")
     (command ".INSERT" "TEE100" "NEA"))

(defun C:TEE125()
     (princ "IKRAM:-")
     (command ".INSERT" "TEE125" "NEA"))

(defun C:TEE150()
     (princ "IKRAM:-")
     (command ".INSERT" "TEE150" "NEA"))

(defun C:TEE200()
     (princ "IKRAM:-")
     (command ".INSERT" "TEE200" "NEA"))

(defun C:EL1125()
     (princ "IKRAM:-")
     (command ".INSERT" "EL1125" "NEA"))

(defun C:EL1150()
     (princ "IKRAM:-")
     (command ".INSERT" "EL1150" "NEA"))

(defun C:EL1165()
     (princ "IKRAM:-")
     (command ".INSERT" "EL1165" "NEA"))

(defun C:EL1175()
     (princ "IKRAM:-")
     (command ".INSERT" "EL1175" "NEA"))

(defun C:EL2225()
     (princ "IKRAM:-")
     (command ".INSERT" "EL2225" "NEA"))

(defun C:EL2232()
     (princ "IKRAM:-")
     (command ".INSERT" "EL2232" "NEA"))

(defun C:EL2240()
     (princ "IKRAM:-")
     (command ".INSERT" "EL2240" "NEA"))

(defun C:EL2250()
     (princ "IKRAM:-")
     (command ".INSERT" "EL2250" "NEA"))

(defun C:EL2265()
     (princ "IKRAM:-")
     (command ".INSERT" "EL2265" "NEA"))

(defun C:EL2275()
     (princ "IKRAM:-")
     (command ".INSERT" "EL2275" "NEA"))

(defun C:EL3050()
     (princ "IKRAM:-")
     (command ".INSERT" "EL3050" "NEA"))

(defun C:EL3065()
     (princ "IKRAM:-")
     (command ".INSERT" "EL3050" "NEA"))

(defun C:EL3075()
     (princ "IKRAM:-")
     (command ".INSERT" "EL3075" "NEA"))

(defun C:EL9025()
     (princ "IKRAM:-")
     (command ".INSERT" "EL9025" "NEA"))

(defun C:EL9032()
     (princ "IKRAM:-")
     (command ".INSERT" "EL9032" "NEA"))

(defun C:EL9040()
     (princ "IKRAM:-")
     (command ".INSERT" "EL9040" "NEA"))

(defun C:EL9050()
     (princ "IKRAM:-")
     (command ".INSERT" "EL9050" "NEA"))

(defun C:EL9065()
     (princ "IKRAM:-")
     (command ".INSERT" "EL9065" "NEA"))

(defun C:EL9075()
     (princ "IKRAM:-")
     (command ".INSERT" "EL9075" "NEA"))

(defun C:EL11100()
     (princ "IKRAM:-")
     (command ".INSERT" "EL11100" "NEA"))

(defun C:EL11125()
     (princ "IKRAM:-")
     (command ".INSERT" "EL11125" "NEA"))

(defun C:EL11150()
     (princ "IKRAM:-")
     (command ".INSERT" "EL11150" "NEA"))

(defun C:EL11200()
     (princ "IKRAM:-")
     (command ".INSERT" "EL11200" "NEA"))

(defun C:EL22100()
     (princ "IKRAM:-")
     (command ".INSERT" "EL22100" "NEA"))

(defun C:EL11250()
     (princ "IKRAM:-")
     (command ".INSERT" "EL11250" "NEA"))

(defun C:EL22150()
     (princ "IKRAM:-")
     (command ".INSERT" "EL22150" "NEA"))

(defun C:EL22125()
     (princ "IKRAM:-")
     (command ".INSERT" "EL22125" "NEA"))

(defun C:EL22200()
     (princ "IKRAM:-")
     (command ".INSERT" "EL22200" "NEA"))

(defun C:EL22250()
     (princ "IKRAM:-")
     (command ".INSERT" "EL22250" "NEA"))

(defun C:EL30100()
     (princ "IKRAM:-")
     (command ".INSERT" "EL30100" "NEA"))

(defun C:EL30125()
     (princ "IKRAM:-")
     (command ".INSERT" "EL30125" "NEA"))

(defun C:EL30150()
     (princ "IKRAM:-")
     (command ".INSERT" "EL30150" "NEA"))

(defun C:EL30200()
     (princ "IKRAM:-")
     (command ".INSERT" "EL30200" "NEA"))

(defun C:EL90100()
     (princ "IKRAM:-")
     (command ".INSERT" "EL90100" "NEA"))

(defun C:EL90125()
     (princ "IKRAM:-")
     (command ".INSERT" "EL90125" "NEA"))

(defun C:EL90150()
     (princ "IKRAM:-")
     (command ".INSERT" "EL90150" "NEA"))

(defun C:EL90200()
     (princ "IKRAM:-")
     (command ".INSERT" "EL90200" "NEA"))

(defun C:EL90250()
     (princ "IKRAM:-")
     (command ".INSERT" "EL90250" "NEA"))

(defun C:EL4525()
     (princ "IKRAM:-")
     (command ".INSERT" "EL4525" "NEA"))

(defun C:EL4532()
     (princ "IKRAM:-")
     (command ".INSERT" "EL4532" "NEA"))

(defun C:EL4540()
     (princ "IKRAM:-")
     (command ".INSERT" "EL4540" "NEA"))

(defun C:EL4550()
     (princ "IKRAM:-")
     (command ".INSERT" "EL4550" "NEA"))

(defun C:EL4565()
     (princ "IKRAM:-")
     (command ".INSERT" "EL4565" "NEA"))

(defun C:EL4575()
     (princ "IKRAM:-")
     (command ".INSERT" "EL4575" "NEA"))

(defun C:EL45100()
     (princ "IKRAM:-")
     (command ".INSERT" "EL45100" "NEA"))

(defun C:EL45125()
     (princ "IKRAM:-")
     (command ".INSERT" "EL45125" "NEA"))

(defun C:EL45150()
     (princ "IKRAM:-")
     (command ".INSERT" "EL45150" "NEA"))

(defun C:EL45200()
     (princ "IKRAM:-")
     (command ".INSERT" "EL45200" "NEA"))

(defun C:EL45250()
     (princ "IKRAM:-")
     (command ".INSERT" "EL45250" "NEA"))

(defun C:EL1550()
     (princ "IKRAM:-")
     (command ".INSERT" "EL1550" "NEA"))

(defun C:EL1565()
     (princ "IKRAM:-")
     (command ".INSERT" "EL1565" "NEA"))

(defun C:EL1575()
     (princ "IKRAM:-")
     (command ".INSERT" "EL1575" "NEA"))

(defun C:EL15100()
     (princ "IKRAM:-")
     (command ".INSERT" "EL15100" "NEA"))

(defun C:EL15150()
     (princ "IKRAM:-")
     (command ".INSERT" "EL15150" "NEA"))

(defun C:EL15200()
     (princ "IKRAM:-")
     (command ".INSERT" "EL15200" "NEA"))

(defun C:EL15250()
     (princ "IKRAM:-")
     (command ".INSERT" "EL15250" "NEA"))

(defun C:RC5025()
     (princ "IKRAM:-")
     (command ".INSERT" "RC5025" "NEA"))

(defun C:RC5032()
     (princ "IKRAM:-")
     (command ".INSERT" "RC5040" "NEA"))

(defun C:RC6540()
     (princ "IKRAM:-")
     (command ".INSERT" "RC6540" "NEA"))

(defun C:RC6550()
     (princ "IKRAM:-")
     (command ".INSERT" "RC6550" "NEA"))

(defun C:RC7525()
     (princ "IKRAM:-")
     (command ".INSERT" "RC7525" "NEA"))

(defun C:RC7550()
     (princ "IKRAM:-")
     (command ".INSERT" "RC7550" "NEA"))

(defun C:RC7565()
     (princ "IKRAM:-")
     (command ".INSERT" "RC7565" "NEA"))

(defun C:RC10050()
     (princ "IKRAM:-")
     (command ".INSERT" "RC10050" "NEA"))

(defun C:RC10065()
     (princ "IKRAM:-")
     (command ".INSERT" "RC10065" "NEA"))

(defun C:RC10075()
     (princ "IKRAM:-")
     (command ".INSERT" "RC10075" "NEA"))

(defun C:CAP25()
     (princ "IKRAM:-")
     (command ".INSERT" "CAP25" "NEA"))

(defun C:CAP32()
     (princ "IKRAM:-")
     (command ".INSERT" "CAP32" "NEA"))

(defun C:CAP40()
     (princ "IKRAM:-")
     (command ".INSERT" "CAP40" "NEA"))

(defun C:CAP50()
     (princ "IKRAM:-")
     (command ".INSERT" "CAP50" "NEA"))

(defun C:CAP65()
     (princ "IKRAM:-")
     (command ".INSERT" "CAP65" "NEA"))

(defun C:CAP75()
     (princ "IKRAM:-")
     (command ".INSERT" "CAP75" "NEA"))

(defun C:CAP100()
     (princ "IKRAM:-")
     (command ".INSERT" "CAP100" "NEA"))

(defun C:CAP150()
     (princ "IKRAM:-")
     (command ".INSERT" "CAP150" "NEA"))

(defun C:CAP200()
     (princ "IKRAM:-")
     (command ".INSERT" "CAP200" "NEA"))

(defun C:CR25()
     (princ "IKRAM:-")
     (command ".INSERT" "CR25" "NEA"))

(defun C:CR32()
     (princ "IKRAM:-")
     (command ".INSERT" "CR32" "NEA"))

(defun C:CR40()
     (princ "IKRAM:-")
     (command ".INSERT" "CR40" "NEA"))

(defun C:CR50()
     (princ "IKRAM:-")
     (command ".INSERT" "CR50" "NEA"))

(defun C:CR65()
     (princ "IKRAM:-")
     (command ".INSERT" "CR65" "NEA"))

(defun C:CR75()
     (princ "IKRAM:-")
     (command ".INSERT" "CR75" "NEA"))

(defun C:CR100()
     (princ "IKRAM:-")
     (command ".INSERT" "CR100" "NEA"))

(defun C:CR150()
     (princ "IKRAM:-")
     (command ".INSERT" "CR150" "NEA"))

(defun C:CR200()
     (princ "IKRAM:-")
     (command ".INSERT" "CR200" "NEA"))

(defun C:CR250()
     (princ "IKRAM:-")
     (command ".INSERT" "CR250" "NEA"))

(defun C:FA2520()
     (princ "IKRAM:-")
     (command ".INSERT" "FA2520" "NEA"))

(defun C:MA25()
     (princ "IKRAM:-")
     (command ".INSERT" "MA25" "NEA"))

(defun C:MA32()
     (princ "IKRAM:-")
     (command ".INSERT" "MA32" "NEA"))

(defun C:MA40()
     (princ "IKRAM:-")
     (command ".INSERT" "MA40" "NEA"))

(defun C:MA50()
     (princ "IKRAM:-")
     (command ".INSERT" "MA50" "NEA"))

(defun C:MA65()
     (princ "IKRAM:-")
     (command ".INSERT" "MA65" "NEA"))

(defun C:MA75()
     (princ "IKRAM:-")
     (command ".INSERT" "MA75" "NEA"))

(defun C:MA100()
     (princ "IKRAM:-")
     (command ".INSERT" "MA100" "NEA"))

(defun C:MA150()
     (princ "IKRAM:-")
     (command ".INSERT" "MA150" "NEA"))

(defun C:MA200()
     (princ "IKRAM:-")
     (command ".INSERT" "MA200" "NEA"))

(defun C:MA250()
     (princ "IKRAM:-")
     (command ".INSERT" "MA250" "NEA"))

(defun C:DH10()
     (princ "IKRAM:-")
     (command ".INSERT" "DH10" "NEA"))

(defun C:DH15()
     (princ "IKRAM:-")
     (command ".INSERT" "DH15" "NEA"))

(defun C:DH20()
     (princ "IKRAM:-")
     (command ".INSERT" "DH20" "NEA"))

(defun C:DH25()
     (princ "IKRAM:-")
     (command ".INSERT" "DH25" "NEA"))

(defun C:DH30()
     (princ "IKRAM:-")
     (command ".INSERT" "DH30" "NEA"))

(defun C:DH35()
     (princ "IKRAM:-")
     (command ".INSERT" "DH35" "NEA"))

(defun C:DH40()
     (princ "IKRAM:-")
     (command ".INSERT" "DH40" "NEA"))

(defun C:DH45()
     (princ "IKRAM:-")
     (command ".INSERT" "DH45" "NEA"))

(defun C:DH50()
     (princ "IKRAM:-")
     (command ".INSERT" "DH50" "NEA"))

(defun C:DH55()
     (princ "IKRAM:-")
     (command ".INSERT" "DH55" "NEA"))

(defun C:DH60()
     (princ "IKRAM:-")
     (command ".INSERT" "DH60" "NEA"))

(defun C:DH65()
     (princ "IKRAM:-")
     (command ".INSERT" "DH65" "NEA"))

(defun C:DH70()
     (princ "IKRAM:-")
     (command ".INSERT" "DH70" "NEA"))

(defun C:DH75()
     (princ "IKRAM:-")
     (command ".INSERT" "DH75" "NEA"))

(defun C:DH80()
     (princ "IKRAM:-")
     (command ".INSERT" "DH80" "NEA"))

(defun C:RC12575()
     (princ "IKRAM:-")
     (command ".INSERT" "RC12575" "NEA"))

(defun C:RC125100()
     (princ "IKRAM:-")
     (command ".INSERT" "RC125100" "NEA"))

(defun C:RC15050()
     (princ "IKRAM:-")
     (command ".INSERT" "RC15050" "NEA"))

(defun C:RC15075()
     (princ "IKRAM:-")
     (command ".INSERT" "RC15075" "NEA"))

(defun C:RC150100()
     (princ "IKRAM:-")
     (command ".INSERT" "RC15075" "NEA"))

(defun C:RC150125()
     (princ "IKRAM:-")
     (command ".INSERT" "RC150125" "NEA"))

(defun C:RC20075()
     (princ "IKRAM:-")
     (command ".INSERT" "RC20075" "NEA"))

(defun C:RC200100()
     (princ "IKRAM:-")
     (command ".INSERT" "RC200100" "NEA"))

(defun C:RC200150()
     (princ "IKRAM:-")
     (command ".INSERT" "RC200150" "NEA"))

(defun C:RC250100()
     (princ "IKRAM:-")
     (command ".INSERT" "RC250100" "NEA"))

(defun C:RC250150()
     (princ "IKRAM:-")
     (command ".INSERT" "RC250150" "NEA"))

(defun C:RC250200()
     (princ "IKRAM:-")
     (command ".INSERT" "RC250200" "NEA"))

(defun C:RT5025()
     (princ "IKRAM:-")
     (command ".INSERT" "RT15025" "NEA"))

(defun C:RT5040()
     (princ "IKRAM:-")
     (command ".INSERT" "RT5040" "NEA"))

(defun C:RT6525()
     (princ "IKRAM:-")
     (command ".INSERT" "RT16525" "NEA"))

(defun C:RT16532()
     (princ "IKRAM:-")
     (command ".INSERT" "RT6532" "NEA"))

(defun C:RT6540()
     (princ "IKRAM:-")
     (command ".INSERT" "RT6540" "NEA"))

(defun C:RT6550()
     (princ "IKRAM:-")
     (command ".INSERT" "RT6550" "NEA"))

(defun C:RT7525()
     (princ "IKRAM:-")
     (command ".INSERT" "RT7525" "NEA"))

(defun C:RT7540()
     (princ "IKRAM:-")
     (command ".INSERT" "RT7540" "NEA"))

(defun C:RT7550()
     (princ "IKRAM:-")
     (command ".INSERT" "RT7550" "NEA"))

(defun C:RT7565()
     (princ "IKRAM:-")
     (command ".INSERT" "RT7565" "NEA"))

(defun C:RT10050()
     (princ "IKRAM:-")
     (command ".INSERT" "RT10050" "NEA"))

(defun C:RT10075()
     (princ "IKRAM:-")
     (command ".INSERT" "RT10075" "NEA"))

(defun C:RT12540()
     (princ "IKRAM:-")
     (command ".INSERT" "RT12540" "NEA"))

(defun C:RT12550()
     (princ "IKRAM:-")
     (command ".INSERT" "RT12550" "NEA"))

(defun C:RT15040()
     (princ "IKRAM:-")
     (command ".INSERT" "RT15040" "NEA"))

(defun C:RT15050()
     (princ "IKRAM:-")
     (command ".INSERT" "RT15050" "NEA"))

(defun C:RT15065()
     (princ "IKRAM:-")
     (command ".INSERT" "RT15065" "NEA"))

(defun C:RT15075()
     (princ "IKRAM:-")
     (command ".INSERT" "RT15075" "NEA"))

(defun C:RT20050()
     (princ "IKRAM:-")
     (command ".INSERT" "RT20050" "NEA"))

(defun C:RT20065()
     (princ "IKRAM:-")
     (command ".INSERT" "RT20065" "NEA"))

(defun C:RT20075()
     (princ "IKRAM:-")
     (command ".INSERT" "RT20075" "NEA"))

(defun C:RT25050()
     (princ "IKRAM:-")
     (command ".INSERT" "RT25050" "NEA"))

(defun C:RT25065()
     (princ "IKRAM:-")
     (command ".INSERT" "RT25065" "NEA"))

(defun C:RT25075()
     (princ "IKRAM:-")
     (command ".INSERT" "RT25075" "NEA"))

(defun C:RT150100()
     (princ "IKRAM:-")
     (command ".INSERT" "RT150100" "NEA"))

(defun C:RT200100()
     (princ "IKRAM:-")
     (command ".INSERT" "RT200100" "NEA"))

(defun C:RT200150()
     (princ "IKRAM:-")
     (command ".INSERT" "RT200150" "NEA"))

(defun C:RT250100()
     (princ "IKRAM:-")
     (command ".INSERT" "RT250100" "NEA"))

(defun C:RT250150()
     (princ "IKRAM:-")
     (command ".INSERT" "RT250150" "NEA"))

(defun C:RT250200()
     (princ "IKRAM:-")
     (command ".INSERT" "RT250200" "NEA"))

(defun C:RISERSTACK()
     (princ "IKRAM:-")
     (command ".INSERT" "RISERSTACK" "NEA"))

(defun C:Riserup2w()
     (princ "IKRAM:-")
     (command ".INSERT" "Riserup2w" "NEA"))

(defun C:Riserupw()
     (princ "IKRAM:-")
     (command ".INSERT" "Riserupw" "NEA"))

(defun C:RT250200()
     (princ "IKRAM:-")
     (command ".INSERT" "RT250200" "NEA"))

(defun C:45w()
     (princ "IKRAM:-")
     (command ".INSERT" "45w" "NEA"))

(defun C:dwn()
     (princ "IKRAM:-")
     (command ".INSERT" "dwn" "NEA"))

(defun C:qbendw()
     (princ "IKRAM:-")
     (command ".INSERT" "qbendw" "NEA"))

(defun C:45dnw()
     (princ "IKRAM:-")
     (command ".INSERT" "45dnw" "NEA"))

(defun C:dnw2()
     (princ "IKRAM:-")
     (command ".INSERT" "dnw2" "NEA"))

(defun C:90dnw()
     (princ "IKRAM:-")
     (command ".INSERT" "90dnw" "NEA"))

(defun C:wr80x65()
     (princ "IKRAM:-")
     (command ".INSERT" "wr80x65" "NEA"))

(defun C:wr100x65()
     (princ "IKRAM:-")
     (command ".INSERT" "wr100x65" "NEA"))

(defun C:wr100x80()
     (princ "IKRAM:-")
     (command ".INSERT" "wr100x80" "NEA"))

(defun C:wr160x80()
     (princ "IKRAM:-")
     (command ".INSERT" "wr160x80" "NEA"))

(defun C:wr160x100()
     (princ "IKRAM:-")
     (command ".INSERT" "wr160x100" "NEA"))

(defun C:teew100()
     (princ "IKRAM:-")
     (command ".INSERT" "teew100" "NEA"))

(defun C:tee65x100()
     (princ "IKRAM:-")
     (command ".INSERT" "tee65x100" "NEA"))

(defun C:tee65x80()
     (princ "IKRAM:-")
     (command ".INSERT" "tee65x80" "NEA"))

(defun C:tee80x65()
     (princ "IKRAM:-")
     (command ".INSERT" "tee80x65" "NEA"))

(defun C:tee80x100()
     (princ "IKRAM:-")
     (command ".INSERT" "tee80x100" "NEA"))

(defun C:cros100()
     (princ "IKRAM:-")
     (command ".INSERT" "cros100" "NEA"))

(defun C:tee160x65()
     (princ "IKRAM:-")
     (command ".INSERT" "tee160x65" "NEA"))

(defun C:wr200x80()
     (princ "IKRAM:-")
     (command ".INSERT" "wr200x80" "NEA"))

(defun C:wr200x160()
     (princ "IKRAM:-")
     (command ".INSERT" "wr200x160" "NEA"))

(defun C:wr250x100()
     (princ "IKRAM:-")
     (command ".INSERT" "wr250x100" "NEA"))

(defun C:wr250x160()
     (princ "IKRAM:-")
     (command ".INSERT" "wr250x160" "NEA"))

(defun C:wr250x200()
     (princ "IKRAM:-")
     (command ".INSERT" "wr250x200" "NEA"))

(defun C:tee160x200()
     (princ "IKRAM:-")
     (command ".INSERT" "tee160x200" "NEA"))

(defun C:tee80x160()
     (princ "IKRAM:-")
     (command ".INSERT" "tee80x160" "NEA"))

(defun C:w100()
     (princ "IKRAM:-")
     (command ".INSERT" "w100" "NEA"))

(defun C:w65x100()
     (princ "IKRAM:-")
     (command ".INSERT" "w65x100" "NEA"))

(defun C:w80x65u()
     (princ "IKRAM:-")
     (command ".INSERT" "w80x65u" "NEA"))

(defun C:w100xs()
     (princ "IKRAM:-")
     (command ".INSERT" "w100xs" "NEA"))

(defun C:w100xsu()
     (princ "IKRAM:-")
     (command ".INSERT" "w100xsu" "NEA"))

(defun C:w100xsd()
     (princ "IKRAM:-")
     (command ".INSERT" "w100xsd" "NEA"))

(defun C:w100xss()
     (princ "IKRAM:-")
     (command ".INSERT" "w100xss" "NEA"))

(defun C:w100xu()
     (princ "IKRAM:-")
     (command ".INSERT" "w100xu" "NEA"))

(defun C:w100x80()
     (princ "IKRAM:-")
     (command ".INSERT" "w100x80" "NEA"))

(defun C:w160x80()
     (princ "IKRAM:-")
     (command ".INSERT" "w160x80" "NEA"))

(defun C:w160x100()
     (princ "IKRAM:-")
     (command ".INSERT" "w160x100" "NEA"))

(defun C:160x100dnw()
     (princ "IKRAM:-")
     (command ".INSERT" "160x100dnw" "NEA"))

(defun C:w160x100u()
     (princ "IKRAM:-")
     (command ".INSERT" "w160x100u" "NEA"))

(defun C:ins250()
     (princ "IKRAM:-")
     (command ".INSERT" "ins250" "NEA"))

(defun C:ins150()
     (princ "IKRAM:-")
     (command ".INSERT" "ins150" "NEA"))

;                              -: THE END :-
;                            =================

;                 HAVE A NICE TIME WITH   ( IKRAM.LSP )
