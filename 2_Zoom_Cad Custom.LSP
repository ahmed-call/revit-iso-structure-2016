(defun c:zP ()
	(command "zoom" "P")
)

(defun c:zA ()
	(command "zoom" "ALL")
)

(defun c:zZ ()
	(command "zoom" "E")
)

(defun c:zX ()
	(command "zoom" ".5X")
)
(defun c:zD ()
	(command "zoom" "D")
)
(defun c:RD ()
	(command "REDO" "Y")
)
(defun c:CBP ()
  (command "COPYBASE" "0,0")
)
(defun c:PBB ()
  (command "PASTEBLOCK" "0,0")
)
(defun c:P0 ()
  (command "PASTECLIP" "0,0")
)
(defun c:OL ()
  (command "LINE" "0,0")
)
(defun c:BXx ()
  (command "-xref" "r" "*")
  (command "-xref" "b" "*" )
  (command "purge" "all" "" "N")
  (command "purge" "all" "" "N")
  (command "purge" "all" "" "N")
  (command "purge" "all" "" "N")
  (command "qsave" "")
)
(defun c:XRE ()
  (command "-xref" "r" "*")
  (command "purge" "all" "" "N")
  (command "purge" "all" "" "N")
  (command "purge" "all" "" "N")
  (command "purge" "all" "" "N")
  (command "qsave" "")
)
(defun C:pu()
	(setq test 1)
	(while (<= test 4)
  	       (Command "purge" "all" "" "n")
	       (setq test (1+ test)
	       )	  
	)


)
(defun c:ea ()
(command "erase" "all" "")
)

(defun c:el ()
(setq e(entlast))
(command "erase" e "")
)
(defun c:es ()
(setq e(getpoint "\nselect object"))
(command "erase" e "")
)
(defun c:u1 ()
(command "ucs" "_ob" pause)
)
