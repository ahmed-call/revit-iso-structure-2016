;				 			  -: WELL COME TO HVAC LAYER :-

                                
(defun C:ACL()
	(princ "\nIKRAM's LAYER SETTINGS :-")
	(setvar "cmdecho" 0)
	(command "layer"
	"n" "M-Ac-Area"         			"c" "3"  			"M-Ac-Area" "P" "N" "M-Ac-Area"
	"n" "M-Ac-Cfm-Text-E"        			"c" "4"  			"M-Ac-Cfm-Text-E" "P" "N" "M-Ac-Cfm-Text-E"
	"n" "M-Ac-Cfm-Text-F"        			"c" "2"  			"M-Ac-Cfm-Text-F" "P" "N" "M-Ac-Cfm-Text-F"
	"n" "M-Ac-Cfm-Text-R"        			"c" "21"  			"M-Ac-Cfm-Text-R" "P" "N" "M-Ac-Cfm-Text-R"
       	"n" "M-Ac-Cfm-Text-S"        			"c" "6"  			"M-Ac-Cfm-Text-S" "P" "N" "M-Ac-Cfm-Text-S"
       	"n" "M-Ac-Cfm-Text-V"    			"c" "1"  			"M-Ac-Cfm-Text-V" "P" "N" "M-Ac-Cfm-Text-V"
	"n" "M-Ac-Beam-opening"             		"c" "2"      	 	"M-Ac-Beam-opening" "P" "N" "M-Ac-Beam-opening"
	"n" "M-Ac-Cd-Pipe"        			"c" "3"  			"M-Ac-Cd-Pipe"
	"n" "M-Ac-Chws"        			"c" "6"  			"M-Ac-Chws"
       	"n" "M-Ac-Chwr"        			"c" "6"  			"M-Ac-chwr" "lt" "center" "M-Ac-Chwr"
       	"n" "M-Ac-Chw-Text"    			"c" "3"  			"M-Ac-Chw-Text"
	"n" "M-Ac-Cws"         			"c" "4"  			"M-Ac-Cws" 
       	"n" "M-Ac-Cwr"         			"c" "4"  			"M-Ac-cwr"  "lt" "center" "M-Ac-Cwr"        
	"n" "M-Ac-Cw-Text"     			"c" "3"  			"M-Ac-Cw-Text"
       	"n" "M-Ac-Diffuser"    			"c" "3"  			"M-Ac-Diffuser"
	"n" "M-Ac-Diffuser-Atrium"     		"c" "3"   			"M-Ac-Diffuser-Atrium" 
 	"n" "M-Ac-Diffuser-Auditorium"     		"c" "3"   			"M-Ac-Diffuser-Auditorium"
	"n" "M-Ac-Diffuser-Text"    			"c" "3"  			"M-Ac-Diffuser-Text"
	"n" "M-Ac-Diffuser-Text-Atrium"      		"c" "3"   			"M-Ac-Diffuser-Text-Atrium" 
 	"n" "M-Ac-Diffuser-Text-Auditorium"   	"c" "3"   			"M-Ac-Diffuser-Text-Auditorium"
	"n" "M-Ac-Duct-Opening-Below"    		"c" "15"  			"M-Ac-Duct-Opening-Below" "lt" "Hidden" "M-Ac-Duct-Opening-Below"
	"n" "M-Ac-Duct-r"      			"c" "21" 			"M-Ac-Duct-r"
	"n" "M-Ac-Duct-r-G01"    			"c"  "21"    		"M-Ac-Duct-r-G01"   
	"n" "M-Ac-Duct-r-G02"    			"c"  "21"    		"M-Ac-Duct-r-G02"   
	"n" "M-Ac-Duct-r-G03"    			"c"  "21"    		"M-Ac-Duct-r-G03"   
	"n" "M-Ac-Duct-r-G04"   			"c"  "21"    		"M-Ac-Duct-r-G04"   
	"n" "M-Ac-Duct-r-G05"    			"c"  "21"    		"M-Ac-Duct-r-G05"   
	"n" "M-Ac-Duct-r-101"   			"c"  "21"    		"M-Ac-Duct-r-101"   
	"n" "M-Ac-Duct-r-102"    			"c"  "21"    		"M-Ac-Duct-r-102"   
	"n" "M-Ac-Duct-r-103"    			"c"  "21"    		"M-Ac-Duct-r-103"   
	"n" "M-Ac-Duct-r-104"    			"c"  "21"   		"M-Ac-Duct-r-104"   
	"n" "M-Ac-Duct-r-105"    			"c"  "21"    		"M-Ac-Duct-r-105"   
	"n" "M-Ac-Duct-r-201"    			"c"  "21"    		"M-Ac-Duct-r-201"   
	"n" "M-Ac-Duct-r-202"    			"c"  "21"    		"M-Ac-Duct-r-202"   
	"n" "M-Ac-Duct-r-203"    			"c"  "21"    		"M-Ac-Duct-r-203"   
	"n" "M-Ac-Duct-r-204"    			"c"  "21"    		"M-Ac-Duct-r-204"   
	"n" "M-Ac-Duct-r-205"    			"c"  "21"    		"M-Ac-Duct-r-205"   
	"n" "M-Ac-Duct-r-301"    			"c"  "21"    		"M-Ac-Duct-r-301"   
	"n" "M-Ac-Duct-r-302"    			"c"  "21"    		"M-Ac-Duct-r-302"   
	"n" "M-Ac-Duct-r-303"    			"c"  "21"    		"M-Ac-Duct-r-303"   
	"n" "M-Ac-Duct-r-304"    			"c"  "21"    		"M-Ac-Duct-r-304"   
	"n" "M-Ac-Duct-r-305"    			"c"  "21"    		"M-Ac-Duct-r-305"   
	"n" "M-Ac-Duct-r-401"    			"c"  "21"    		"M-Ac-Duct-r-401"   
	"n" "M-Ac-Duct-r-402"    			"c"  "21"    		"M-Ac-Duct-r-402"   
	"n" "M-Ac-Duct-r-403"    			"c"  "21"    		"M-Ac-Duct-r-403"   
	"n" "M-Ac-Duct-r-404"    			"c"  "21"    		"M-Ac-Duct-r-404"   
	"n" "M-Ac-Duct-r-405"    			"c"  "21"    		"M-Ac-Duct-r-405"
	"n" "M-Ac-Duct-r-atrium"      		"c" "63"    		"M-Ac-Duct-r-atrium"  
	"n" "M-Ac-Duct-r-auditorium"     		"c" "63"    		"M-Ac-Duct-r-auditorium"
	"n" "M-Ac-Duct-r-mech" 			"c" "63"  			"M-Ac-Duct-r-mech"
	"n" "M-Ac-Duct-s"      			"c" "6"  			"M-Ac-Duct-s"
	"n" "M-Ac-Duct-s-G01"   			"c"  "6"     		"M-Ac-Duct-s-G01"   
	"n" "M-Ac-Duct-s-G02"    			"c"  "6"     		"M-Ac-Duct-s-G02"   
	"n" "M-Ac-Duct-s-G03"    			"c"  "6"     		"M-Ac-Duct-s-G03"   
	"n" "M-Ac-Duct-s-G04"    			"c"  "6"     		"M-Ac-Duct-s-G04"   
	"n" "M-Ac-Duct-s-G05"    			"c"  "6"     		"M-Ac-Duct-s-G05"   
	 "n" "M-Ac-Duct-s-101"    			"c"  "6"     		"M-Ac-Duct-s-101"   
	"n" "M-Ac-Duct-s-102"    			"c"  "6"     		"M-Ac-Duct-s-102"   
	"n" "M-Ac-Duct-s-103"    			"c"  "6"     		"M-Ac-Duct-s-103"   
	"n" "M-Ac-Duct-s-104"    			"c"  "6"     		"M-Ac-Duct-s-104"   
	"n" "M-Ac-Duct-s-105"    			"c"  "6"     		"M-Ac-Duct-s-105"   
	"n" "M-Ac-Duct-s-201"    			"c"  "6"     		"M-Ac-Duct-s-201"   
	"n" "M-Ac-Duct-s-202"    			"c"  "6"     		"M-Ac-Duct-s-202"   
	"n" "M-Ac-Duct-s-203"    			"c"  "6"     		"M-Ac-Duct-s-203"   
	"n" "M-Ac-Duct-s-204"    			"c"  "6"     		"M-Ac-Duct-s-204"   
	"n" "M-Ac-Duct-s-205"    			"c"  "6"     		"M-Ac-Duct-s-205"   
	"n" "M-Ac-Duct-s-301"    			"c"  "6"     		"M-Ac-Duct-s-301"   
	"n" "M-Ac-Duct-s-302"    			"c"  "6"     		"M-Ac-Duct-s-302"   
	"n" "M-Ac-Duct-s-303"    			"c"  "6"     		"M-Ac-Duct-s-303"   
	"n" "M-Ac-Duct-s-304"    			"c"  "6"     		"M-Ac-Duct-s-304"   
	"n" "M-Ac-Duct-s-305"    			"c"  "6"     		"M-Ac-Duct-s-305"   
	"n" "M-Ac-Duct-s-401"    			"c"  "6"     		"M-Ac-Duct-s-401"   
	"n" "M-Ac-Duct-s-402"    			"c"  "6"     		"M-Ac-Duct-s-402"   
	"n" "M-Ac-Duct-s-403"    			"c"  "6"     		"M-Ac-Duct-s-403"   
	"n" "M-Ac-Duct-s-404"    			"c"  "6"     		"M-Ac-Duct-s-404"   
	"n" "M-Ac-Duct-s-405"    			"c"  "6"     		"M-Ac-Duct-s-405"   
	"n" "M-Ac-Duct-s-atrium"      		"c" "144"    		"M-Ac-Duct-s-atrium"  
	"n" "M-Ac-Duct-s-auditorium"     		"c" "144"    		"M-Ac-Duct-s-auditorium"
	"n" "M-Ac-Duct-s-mech" 			"c" "144"  		"M-Ac-Duct-s-mech"
	"n" "M-Ac-Duct-vav"    			"c" "4"  			"M-Ac-Duct-vav"
	"n" "M-Ac-Exhaust-Atrium"  			"c" "44"			"M-Ac-Exhaust-Atrium"
	"n" "M-Ac-Exhaust-Auditorium"  		"c" "44"			"M-Ac-Exhaust-Auditorium"
	"n" "M-Ac-Exhaust-Basement"     		"c" "6"  			"M-Ac-Exhaust-Basement"
	"n" "M-Ac-Exhaust-Chamical"		"c" "30"  			"M-Ac-Exhaust-Chamical"
	"n" "M-Ac-Exhaust-Clean"	 		"c" "3"  			"M-Ac-Exhaust-Clean"
	"n" "M-Ac-Exhaust-Dirty"	 		"c" "5"			"M-Ac-Exhaust-Dirty"
	"n" "M-Ac-Exhaust-Fm200"	 		"c" "30"			"M-Ac-Exhaust-Fm200"
	"n" "M-Ac-Exhaust-Generator"	 	"c" "5"			"M-Ac-Exhaust-Generator"
	"n" "M-Ac-Exhaust-Hood"       		"c" "220"  		"M-Ac-Exhaust-Hood" "lt" "HIDDEN" "M-Ac-Exhaust-Hood"   
	"n" "M-Ac-Exhaust-Hydrofluoric Acid" 		"c" "40"  			"M-Ac-Exhaust-Hydrofluoric Acid"
	"n" "M-Ac-Exhaust-Isolation"  		"c" "30"  			"M-Ac-Exhaust-Isolation"
	"n" "M-Ac-Exhaust-Kitchen" 			"c" "200"  		"M-Ac-Exhaust-Kitchen"
	"n" "M-Ac-Exhaust-Lab"   			"c" "144"  		"M-Ac-Exhaust-Lab"
	"n" "M-Ac-Exhaust-Mri"   			"c" "30"  			"M-Ac-Exhaust-Mri"
	"n" "M-Ac-Exhaust-Perchloric-Acid"   		"c" "5"  			"M-Ac-Exhaust-Perchloric-Acid"
	"n" "M-Ac-Exhaust-Radioactive"   		"c" "40"  			"M-Ac-Exhaust-Radioactive"
	"n" "M-Ac-Exhaust-Relief"   			"c" "104"  		"M-Ac-Exhaust-Relief"
	"n" "M-Ac-Exhaust-Smoke"        		"c" "5"     		"M-Ac-Exhaust-Smoke"
	"n" "M-Ac-Fire-dampeer" 	   		"c" "3"  			"M-Ac-Fire-dampeer"
	"n" "M-Ac-Freshair-Atrium" 			"c" "40"  			"M-Ac-Freshair-Atrium"
	"n" "M-Ac-Freshair-Basement"    		"c" "40"  			"M-Ac-Freshair-Basement"
	"n" "M-Ac-Freshair-Fm200"  			"c" "3"  			"M-Ac-Freshair-Fm200"
	"n" "M-Ac-Freshair-Generator"  		"c" "4"  			"M-Ac-Freshair-Generator"
	"n" "M-Ac-Freshair-Kitchen"  		"c" "60"  			"M-Ac-Freshair-Kitchen"
	"n" "M-Ac-Freshair-Normal"    		"c" "3"   			"M-Ac-Freshair-Normal"   
	"n" "M-Ac-Freshair-Smoke"     		"c" "60"    		"M-Ac-Freshair-Smoke"
	"n" "M-Ac-Freshair-Stair"     			"c" "40"    		"M-Ac-Freshair-Stair"
	"n" "M-Ac-Grille"      			"c" "3"  			"M-Ac-Grille"
	"n" "M-Ac-Grille-Text"  			"c" "3"  			"M-Ac-Grille-text"
	"n" "M-Ac-Hrps"         			"c" "3"  			"M-Ac-Hrps"
        	"n" "M-Ac-Hrpr"         			"c" "3"  			"M-Ac-Hrpr" "lt" "center" "M-Ac-Hrpr"
        	"n" "M-Ac-Hrp-Text"     			"c" "3" 		 	"M-Ac-Hrp-Text"        	
	"n" "M-Ac-Hws"         			"c" "4"  			"M-Ac-Hws"
        	"n" "M-Ac-Hwr"         			"c" "4"  			"M-Ac-Hwr" "lt" "center" "M-Ac-Hwr"
        	"n" "M-Ac-Hw-Text"     			"c" "3"  			"M-Ac-Hw-Text"
	"n" "M-Ac-Lab-Hood"        			"c" "15"		  	"M-Ac-Lab-Hood" "lt" "Hidden" "M-Ac-Lab-Hood"
	"n" "M-Ac-Louver-Exhaust"  			"c" "5"  			"M-Ac-Louver-Exhaust"
	"n" "M-Ac-Louver-Freshair"  			"c" "4"  			"M-Ac-Louver-Freshair"
	"n" "M-Ac-Louvered-Penthouse"        		"c" "4"		  	"M-Ac-Louvered-Penthouse"
	"n" "M-Ac-Line"        			"c" "2"		  	"M-Ac-Line"
	"n" "M-Ac-Line-Text"        			"c" "3"		  	"M-Ac-Line-Text"
	"n" "M-Ac-Plumbing"    			"c" "2"  			"M-Ac-Plumbing"
	"n" "M-Ac-Revision"    			"c" "4"  			"M-Ac-Revision"
	"n" "M-Ac-Rsl-Pipe"         			"c" "3"  			"M-Ac-Rsl-Pipe" 
       	"n" "M-Ac-Rll-Pipe"         			"c" "3"  			"M-Ac-rll-Pipe"  "lt" "center" "M-Ac-Rll-Pipe"
	"n" "M-Ac-Text"        			"c" "3"  			"M-Ac-Text"
	"n" "M-Ac-Text-Apf"        			"c" "3"  			"M-Ac-Text-Apf"
	"n" "M-Ac-Unit"        			"c" "4"  			"M-Ac-Unit" 
	"n" "M-Ac-Zone"              			"c" "1"			"M-Ac-Zone" "P" "N" "M-Ac-Zone"	
	"n" "DefPoints"      				"c" "7"  			"DefPoints"
	"n" "Viewport"       				"c" "1"  			"Viewport"	   
	"n" "M-XREF"           			"c" "8"   			"M-XREF" "")
	(princ "[--- DONE ---]"))
           

;				   -: WELL COME TO HVAC LAYER :-

(defun C:CFF() 		(princ "IKRAM:-") 		(command "layer" "set" "M-Ac-Cfm-Text-F" ""))
(defun C:CFE() 		(princ "IKRAM:-") 		(command "layer" "set" "M-Ac-Cfm-Text-E" ""))
(defun C:CFR() 		(princ "IKRAM:-") 		(command "layer" "set" "M-Ac-Cfm-Text-R" ""))
(defun C:CFS() 		(princ "IKRAM:-") 		(command "layer" "set" "M-Ac-Cfm-Text-S" ""))
(defun C:CFV() 		(princ "IKRAM:-") 		(command "layer" "set" "M-Ac-Cfm-Text-V" ""))
(defun C:ACA() 		(princ "IKRAM:-") 		(command "layer" "set" "M-Ac-area" ""))
(defun C:CHWS() 		(princ "IKRAM:-") 		(command "layer" "set" "M-Ac-chws" "")) 
(defun C:CHWR() 		(princ "IKRAM:-")		(command "layer" "set" "M-Ac-chwr" ""))
(defun C:CHWT() 		(princ "IKRAM:-")		(command "layer" "set" "M-Ac-Chw-Text" ""))
(defun C:CWS() 		(princ "IKRAM:-") 		(command "layer" "set" "M-Ac-cws" "")) 
(defun C:CWR() 		(princ "IKRAM:-") 		(command "layer" "set" "M-Ac-cwr" ""))
(defun C:CWT() 		(princ "IKRAM:-") 		(command "layer" "set" "M-Ac-Cw-Text" ""))
(defun C:ACDF() 		(princ "IKRAM:-") 		(command "layer" "set" "M-Ac-diffuser" ""))
(defun C:ACDT() 		(princ "IKRAM:-") 		(command "layer" "set" "M-Ac-Diffuser-Text" ""))
(defun C:ACS() 		(princ "IKRAM:-") 		(command "layer" "set" "M-Ac-duct-s" ""))
(defun C:ACR() 		(princ "IKRAM:-") 		(command "layer" "set" "M-Ac-duct-r" ""))
(defun C:ACV() 		(princ "IKRAM:-") 		(command "layer" "set" "M-Ac-duct-VAV" ""))
(defun C:ACEB() 		(princ "IKRAM:-") 		(command "layer" "set" "M-Ac-Exhaust-Basement" ""))
(defun C:ACEC() 		(princ "IKRAM:-") 		(command "layer" "set" "M-Ac-Exhaust-Clean" ""))
(defun C:ACED() 		(princ "IKRAM:-") 		(command "layer" "set" "M-Ac-Exhaust-Dirty" ""))
(defun C:ACEG() 		(princ "IKRAM:-") 		(command "layer" "set" "M-Ac-Exhaust-Generator" ""))
(defun C:ACEK() 		(princ "IKRAM:-") 		(command "layer" "set" "M-Ac-Exhaust-Kitchen" ""))
(defun C:ACB() 		(princ "IKRAM:-") 		(command "layer" "set" "M-Ac-Exhaust-Lab" ""))
(defun C:ACEI()		(princ "IKRAM:-") 		(command "layer" "set" "M-Ac-Exhaust-Isolation" ""))
(defun C:ACEM() 		(princ "IKRAM:-") 		(command "layer" "set" "M-Ac-Exhaust-Mri" ""))
(defun C:ACER() 		(princ "IKRAM:-") 		(command "layer" "set" "M-Ac-Exhaust-Relief" ""))
(defun C:ACES() 		(princ "IKRAM:-") 		(command "layer" "set" "M-Ac-Exhaust-Smoke" ""))
(defun C:ACFB() 		(princ "IKRAM:-") 		(command "layer" "set" "M-Ac-Freshair-Basement" ""))
(defun C:ACFA() 		(princ "IKRAM:-") 		(command "layer" "set" "M-Ac-Freshair-Atriuml" ""))
(defun C:ACFG() 		(princ "IKRAM:-")		(command "layer" "set" "M-Ac-Freshair-Generator" ""))
(defun C:ACFK() 		(princ "IKRAM:-")		(command "layer" "set" "M-Ac-Freshair-Kitchen" ""))
(defun C:ACFN() 		(princ "IKRAM:-")		(command "layer" "set" "M-Ac-Freshair-Normal" ""))
(defun C:ACFS() 		(princ "IKRAM:-")		(command "layer" "set" "M-Ac-Freshair-Smoke" ""))
(defun C:ACFST() 		(princ "IKRAM:-")		(command "layer" "set" "M-Ac-Freshair-Stair" ""))
(defun C:ACG() 		(princ "IKRAM:-") 		(command "layer" "set" "M-Ac-grille" ""))
(defun C:HWS() 		(princ "IKRAM:-") 		(command "layer" "set" "M-Ac-Hws" ""))
(defun C:HWR() 		(princ "IKRAM:-") 		(command "layer" "set" "M-Ac-Hwr" ""))
(defun C:HWT() 		(princ "IKRAM:-") 		(command "layer" "set" "M-Ac-Hw-Text" ""))
(defun C:ACLP() 		(princ "IKRAM:-") 		(command "layer" "set" "M-Ac-Louvered-Penthouse" ""))
(defun C:ACLI() 		(princ "IKRAM:-") 		(command "layer" "set" "M-Ac-line" ""))
(defun C:ACLT() 		(princ "IKRAM:-") 		(command "layer" "set" "M-Ac-Line-Text" ""))
(defun C:ACFD() 		(princ "IKRAM:-") 		(command "layer" "set" "M-Ac-Fire-dampeer" ""))
(defun C:ACT() 		(princ "IKRAM:-") 		(command "layer" "set" "M-Ac-text" "")) 
(defun C:ACTA() 		(princ "IKRAM:-") 		(command "layer" "set" "M-Ac-text-Apf" ""))
(defun C:ACP() 		(princ "IKRAM:-") 		(command "layer" "set" "M-Ac-Plumbing" ""))
(defun C:ACRV() 		(princ "IKRAM:-") 		(command "layer" "set" "M-Ac-Revision" ""))
(defun C:ACU() 		(princ "IKRAM:-") 		(command "layer" "set" "M-Ac-unit" ""))
(defun C:ACZ() 		(princ "IKRAM:-") 		(command "layer" "set" "M-Ac-zone" ""))
(defun C:DEF() 		(princ "IKRAM:-") 		(command "layer" "set" "DefPoints" ""))
(defun C:XRF() 		(princ "IKRAM:-") 		(command "layer" "set" "M-Xref" ""))
(defun C:ACVP()		(princ "IKRAM:-") 		(command "layer" "set" "Viewport" ""))
(defun C:OF() 		(princ "IKRAM:-") 		(command ".layer" "off" "*" "" ""))
(defun C:ON()		(princ "IKRAM:-") 		(command ".layer" "on" "*" ""))



;                   	 				          -: THE END :-
;                  					      =================

;           			 	    WORK HARD & HAVE A NICE TIME WITH   ( IKRAM.LSP )
